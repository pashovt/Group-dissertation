Attribute VB_Name = "ChannelGenerator"
'Const X1 = -40, Y1 = -40, Z1 = 40, Radius1 = 5, X2 = 50, Y2 = -40, Z2 = 40, Radius2 = 5
Public Sub CATMain(X1 As Integer, Y1 As Integer, Z1 As Integer, Radius1 As Integer, X2 As Integer, Y2 As Integer, Z2 As Integer, Radius2 As Integer)

'---------------------------------------------------------------------------'
' Generates the values for the START plane equation
Dim A1, B1, C1, D1
A1 = X2 - X1
B1 = Y2 - Y1
C1 = Z2 - Z1
D1 = (A1 * X1 + B1 * Y1 + C1 * Z1)

' Generates the values for the END plane equation
Dim A2, B2, C2, D2
A2 = X1 - X2
B2 = Y1 - Y2
C2 = Z1 - Z2
D2 = (A2 * X2 + B2 * Y2 + C2 * Z2)


'---------------------------------------------------------------------------'
' Main part of CATIA documentation
Dim partDocument1, part1
' Retrieve your active document
Set partDocument1 = CATIA.ActiveDocument
Set part1 = partDocument1.Part

'---------------------------------------------------------------------------'
Dim partName, bodyName, Bodies
' Extracts the active part name
partName = partDocument1.Product.Name
' Scans the collection of Bodies in a part
Set Bodies = partDocument1.Part.Bodies
'counter = Bodies.Count
bodyName = Bodies.Item(1).Name
Path = partName & "\" & bodyName

'---------------------------------------------------------------------------'
Dim hybridShapeFactory1
Set hybridShapeFactory1 = part1.HybridShapeFactory

' Generates the reference point for the START plane
Dim hybridShapePointCoord1, bodies1, body1, hybridShapePointCoord2
Set hybridShapePointCoord1 = hybridShapeFactory1.AddNewPointCoord(X1, Y1, Z1)
Set bodies1 = part1.Bodies
Set body1 = bodies1.Item(bodyName)
body1.InsertHybridShape hybridShapePointCoord1
part1.InWorkObject = hybridShapePointCoord1
part1.Update
' Generates the reference point for the END plane
Set hybridShapePointCoord2 = hybridShapeFactory1.AddNewPointCoord(X2, Y2, Z2)
body1.InsertHybridShape hybridShapePointCoord2
part1.InWorkObject = hybridShapePointCoord2
part1.Update

' Generates the START plane using the equation and the reference point
Dim hybridShapePlaneEquation1, reference1, hybridShapePlaneEquation2, reference2
Set hybridShapePlaneEquation1 = hybridShapeFactory1.AddNewPlaneEquation(A1, B1, C1, D1)
Set reference1 = part1.CreateReferenceFromObject(hybridShapePointCoord1)
hybridShapePlaneEquation1.SetReferencePoint reference1
body1.InsertHybridShape hybridShapePlaneEquation1
part1.InWorkObject = hybridShapePlaneEquation1
part1.Update
' Generates the END plane using the equation and the reference point
Set hybridShapePlaneEquation2 = hybridShapeFactory1.AddNewPlaneEquation(A2, B2, C2, D2)
Set reference2 = part1.CreateReferenceFromObject(hybridShapePointCoord2)
hybridShapePlaneEquation2.SetReferencePoint reference2
body1.InsertHybridShape hybridShapePlaneEquation2
part1.InWorkObject = hybridShapePlaneEquation2
part1.Update


'---------------------------------------------------------------------------'
' Creates a selection
Dim selection1, FirstPoint, SecondPoint
Set selection1 = partDocument1.Selection

' Traverses the selection for a specified named component
' Finds the needed point names
selection1.Search ("Name=point*,all")
selectionCount = selection1.Count2
FirstPoint = selectionCount - 1
SecondPoint = selectionCount
' Gets the name of the needed point - to be used as a reference - supports the automation of the tool
FirstPointName = selection1.Item(FirstPoint).Value.Name
SecondPointName = selection1.Item(SecondPoint).Value.Name

' Finds the needed plane names
Dim FirstPlane, SecondPlane
selection1.Search ("Name=plane*,all")
selectionCount = selection1.Count2
FirstPlane = selectionCount - 1
SecondPlane = selectionCount
FirstPlaneName = selection1.Item(FirstPlane).Value.Name
SecondPlaneName = selection1.Item(SecondPlane).Value.Name

'---------------------------------------------------------------------------'
' Generates a circle on the START planes - with specified point coordinates
Dim sketches1, hybridShapes1, reference3, sketch1, arrayOfVariantOfDouble1(8)
Dim factory2D1, geometricElements1, axis2D1, line2D1, line2D2, point2D1
Dim circle2D1, constraints1, reference4, reference5, constraint1, length1
Dim reference6, reference7, constraint2, length2, reference8, constraint3, length3
Set sketches1 = body1.Sketches
Set hybridShapes1 = body1.HybridShapes
Set reference3 = hybridShapes1.Item(FirstPlaneName)
Set sketch1 = sketches1.Add(reference3)
arrayOfVariantOfDouble1(0) = 0#
arrayOfVariantOfDouble1(1) = 0#
arrayOfVariantOfDouble1(2) = 0#
arrayOfVariantOfDouble1(3) = 0#
arrayOfVariantOfDouble1(4) = 0#
arrayOfVariantOfDouble1(5) = 0#
arrayOfVariantOfDouble1(6) = 0#
arrayOfVariantOfDouble1(7) = 0#
arrayOfVariantOfDouble1(8) = 0#
Set sketch1Variant = sketch1
sketch1Variant.SetAbsoluteAxisData arrayOfVariantOfDouble1
part1.InWorkObject = sketch1
Set factory2D1 = sketch1.OpenEdition()
Set geometricElements1 = sketch1.GeometricElements
Set axis2D1 = geometricElements1.Item("AbsoluteAxis")
Set line2D1 = axis2D1.GetItem("HDirection")
line2D1.ReportName = 1
Set line2D2 = axis2D1.GetItem("VDirection")
line2D2.ReportName = 2
Set point2D1 = factory2D1.CreatePoint(0#, 0#)
point2D1.ReportName = 3
Set circle2D1 = factory2D1.CreateClosedCircle(0#, 0#, Radius1)
circle2D1.CenterPoint = point2D1
circle2D1.ReportName = 4
Set constraints1 = sketch1.Constraints
Set reference4 = part1.CreateReferenceFromObject(point2D1)
Set reference5 = part1.CreateReferenceFromObject(line2D2)
Set constraint1 = constraints1.AddBiEltCst(catCstTypeDistance, reference4, reference5)
constraint1.Mode = catCstModeDrivingDimension
Set length1 = constraint1.Dimension
length1.Value = 0#
Set reference6 = part1.CreateReferenceFromObject(point2D1)
Set reference7 = part1.CreateReferenceFromObject(line2D1)
Set constraint2 = constraints1.AddBiEltCst(catCstTypeDistance, reference6, reference7)
constraint2.Mode = catCstModeDrivingDimension
Set length2 = constraint2.Dimension
length2.Value = 0#
Set reference8 = part1.CreateReferenceFromObject(circle2D1)
Set constraint3 = constraints1.AddMonoEltCst(catCstTypeRadius, reference8)
constraint3.Mode = catCstModeDrivingDimension
Set length3 = constraint3.Dimension
length3.Value = Radius1
sketch1.CloseEdition
part1.InWorkObject = sketch1
part1.Update



' Generates a circle on the END planes - with specified point coordinates
Dim reference9, sketch2, arrayOfVariantOfDouble2(8), factory2D2, geometricElements2
Dim axis2D2, line2D3, line2D4, point2D2, circle2D2, constraints2, reference10
Dim reference11, constraint4, length4, reference12, reference13, constraint5
Dim length5, reference14, constraint6, length6
Set reference9 = hybridShapes1.Item(SecondPlaneName)
Set sketch2 = sketches1.Add(reference9)
arrayOfVariantOfDouble2(0) = 0#
arrayOfVariantOfDouble2(1) = 0#
arrayOfVariantOfDouble2(2) = 0#
arrayOfVariantOfDouble2(3) = 0#
arrayOfVariantOfDouble2(4) = 0#
arrayOfVariantOfDouble2(5) = 0#
arrayOfVariantOfDouble2(6) = 0#
arrayOfVariantOfDouble2(7) = 0#
arrayOfVariantOfDouble2(8) = 0#
Set sketch2Variant = sketch2
sketch2Variant.SetAbsoluteAxisData arrayOfVariantOfDouble2
part1.InWorkObject = sketch2
Set factory2D2 = sketch2.OpenEdition()
Set geometricElements2 = sketch2.GeometricElements
Set axis2D2 = geometricElements2.Item("AbsoluteAxis")
Set line2D3 = axis2D2.GetItem("HDirection")
line2D3.ReportName = 1
Set line2D4 = axis2D2.GetItem("VDirection")
line2D4.ReportName = 2
Set point2D2 = factory2D2.CreatePoint(0#, 0#)
point2D2.ReportName = 3
Set circle2D2 = factory2D2.CreateClosedCircle(0#, 0#, Radius2)
circle2D2.CenterPoint = point2D2
circle2D2.ReportName = 4
Set constraints2 = sketch2.Constraints
Set reference10 = part1.CreateReferenceFromObject(point2D2)
Set reference11 = part1.CreateReferenceFromObject(line2D4)
Set constraint4 = constraints2.AddBiEltCst(catCstTypeDistance, reference10, reference11)
constraint4.Mode = catCstModeDrivingDimension
Set length4 = constraint4.Dimension
length4.Value = 0#
Set reference12 = part1.CreateReferenceFromObject(point2D2)
Set reference13 = part1.CreateReferenceFromObject(line2D3)
Set constraint5 = constraints2.AddBiEltCst(catCstTypeDistance, reference12, reference13)
constraint5.Mode = catCstModeDrivingDimension
Set length5 = constraint5.Dimension
length5.Value = 0#
Set reference14 = part1.CreateReferenceFromObject(circle2D2)
Set constraint6 = constraints2.AddMonoEltCst(catCstTypeRadius, reference14)
constraint6.Mode = catCstModeDrivingDimension
Set length6 = constraint6.Dimension
length6.Value = Radius2
sketch2.CloseEdition
part1.InWorkObject = sketch2
part1.Update


'---------------------------------------------------------------------------'
' Generates an extremum for START plane
Dim hybridShapeDirection1, reference15, hybridShapeExtremum1
Set hybridShapeDirection1 = hybridShapeFactory1.AddNewDirectionByCoord(1#, 2#, 3#)
Set reference15 = part1.CreateReferenceFromObject(sketch1)
Set hybridShapeExtremum1 = hybridShapeFactory1.AddNewExtremum(reference15, hybridShapeDirection1, 1)
body1.InsertHybridShape hybridShapeExtremum1
part1.InWorkObject = hybridShapeExtremum1
part1.Update
' Generates an extremum for END plane
Dim hybridShapeDirection2, reference16, hybridShapeExtremum2
Set hybridShapeDirection2 = hybridShapeFactory1.AddNewDirectionByCoord(1#, 2#, 3#)
Set reference16 = part1.CreateReferenceFromObject(sketch2)
Set hybridShapeExtremum2 = hybridShapeFactory1.AddNewExtremum(reference16, hybridShapeDirection2, 1)
body1.InsertHybridShape hybridShapeExtremum2
part1.InWorkObject = hybridShapeExtremum2
part1.Update


'---------------------------------------------------------------------------'
' Removes the solid that is between the circles generated on the START and END planes
Dim shapeFactory1, loft1, hybridShapeLoft1, reference17, reference18, reference19, reference20
Set shapeFactory1 = part1.ShapeFactory
Set loft1 = shapeFactory1.AddNewRemovedLoft()
Set hybridShapeLoft1 = loft1.HybridShape
hybridShapeLoft1.SectionCoupling = 3
hybridShapeLoft1.Relimitation = 1
hybridShapeLoft1.CanonicalDetection = 2
Set reference17 = part1.CreateReferenceFromObject(sketch1)
Set reference18 = part1.CreateReferenceFromObject(hybridShapeExtremum1)
hybridShapeLoft1.AddSectionToLoft reference17, 1, reference18
Set reference19 = part1.CreateReferenceFromObject(sketch2)
Set reference20 = part1.CreateReferenceFromObject(hybridShapeExtremum2)
hybridShapeLoft1.AddSectionToLoft reference19, -1, reference20
part1.InWorkObject = hybridShapeLoft1
part1.Update

'---------------------------------------------------------------------------'
' Finds the needed sketch names
Dim FirstSketch, SecondSketch
selection1.Search ("Name=Sketch*,all")
selectionCount = selection1.Count2
FirstSketch = selectionCount - 1
SecondSketch = selectionCount
FirstSketchName = selection1.Item(FirstSketch).Value.Name
SecondSketchName = selection1.Item(SecondSketch).Value.Name
' Finds the needed extremum names
Dim FirstExtremum, SecondExtremum
selection1.Search ("Name=Extremum*,all")
selectionCount = selection1.Count2
FirstExtremum = selectionCount - 1
SecondExtremum = selectionCount
FirstExtremumName = selection1.Item(FirstExtremum).Value.Name
SecondExtremumName = selection1.Item(SecondExtremum).Value.Name


'---------------------------------------------------------------------------'
' Hides the specified points
HiddingObjects "Point", FirstPointName, bodyName
HiddingObjects "Point", SecondPointName, bodyName
' Hides the specified planes
HiddingObjects "Plane", FirstPlaneName, bodyName
HiddingObjects "Plane", SecondPlaneName, bodyName
' Hides the specified sketches
HiddingObjects "Sketch", FirstSketchName, bodyName
HiddingObjects "Sketch", SecondSketchName, bodyName
' Hides the specified extremums
HiddingObjects "Extremum", FirstExtremumName, bodyName
HiddingObjects "Extremum", SecondExtremumName, bodyName


'---------------------------------------------------------------------------'
' Generating the Groove solid removal
Dim sketch3, arrayOfVariantOfDouble3(8), factory2D3, geometricElements3, axis2D3, line2D5
Dim line2D6, point2D3, point2D4, point2D5, circle2D3, constraints3, reference21, reference22
Dim constraint7, length7, reference23, reference24, constraint8, length8
Dim reference25, constraint9, length9, reference26, reference27, constraint10
Set sketch3 = sketches1.Add(reference3)
arrayOfVariantOfDouble3(0) = 0#
arrayOfVariantOfDouble3(1) = 0#
arrayOfVariantOfDouble3(2) = 0#
arrayOfVariantOfDouble3(3) = 0#
arrayOfVariantOfDouble3(4) = 0#
arrayOfVariantOfDouble3(5) = 0#
arrayOfVariantOfDouble3(6) = 0#
arrayOfVariantOfDouble3(7) = 0#
arrayOfVariantOfDouble3(8) = 0#
Set sketch3Variant = sketch3
sketch3Variant.SetAbsoluteAxisData arrayOfVariantOfDouble3
part1.InWorkObject = sketch3
Set factory2D3 = sketch3.OpenEdition()
Set geometricElements3 = sketch3.GeometricElements
Set axis2D3 = geometricElements3.Item("AbsoluteAxis")
Set line2D5 = axis2D3.GetItem("HDirection")
line2D5.ReportName = 2
Set line2D6 = axis2D3.GetItem("VDirection")
line2D6.ReportName = 3
Set point2D3 = factory2D3.CreatePoint(0#, 0#)
point2D3.ReportName = 4
Set point2D4 = factory2D3.CreatePoint(-Radius1, 0#)
point2D4.ReportName = 5
Set point2D5 = factory2D3.CreatePoint(Radius1, 0#)
point2D5.ReportName = 6
Set circle2D3 = factory2D3.CreateCircle(0#, 0#, Radius1, 3.141593, 6.283185)
circle2D3.CenterPoint = point2D3
circle2D3.ReportName = 7
circle2D3.StartPoint = point2D4
circle2D3.EndPoint = point2D5
Set constraints3 = sketch3.Constraints
Set reference21 = part1.CreateReferenceFromObject(point2D3)
Set reference22 = part1.CreateReferenceFromObject(line2D6)
Set constraint7 = constraints3.AddBiEltCst(catCstTypeDistance, reference21, reference22)
constraint7.Mode = catCstModeDrivingDimension
Set length7 = constraint7.Dimension
length7.Value = 0#
Set reference23 = part1.CreateReferenceFromObject(point2D3)
Set reference24 = part1.CreateReferenceFromObject(line2D5)
Set constraint8 = constraints3.AddBiEltCst(catCstTypeDistance, reference23, reference24)
constraint8.Mode = catCstModeDrivingDimension
Set length8 = constraint8.Dimension
length8.Value = 0#
Set reference25 = part1.CreateReferenceFromObject(circle2D3)
Set constraint9 = constraints3.AddMonoEltCst(catCstTypeRadius, reference25)
constraint9.Mode = catCstModeDrivingDimension
Set length9 = constraint9.Dimension
length9.Value = Radius1
Set reference26 = part1.CreateReferenceFromObject(point2D4)
Set reference27 = part1.CreateReferenceFromObject(line2D5)
Set constraint10 = constraints3.AddBiEltCst(catCstTypeOn, reference26, reference27)
constraint10.Mode = catCstModeDrivingDimension
sketch3.CloseEdition
part1.InWorkObject = sketch3
part1.Update


Dim sketch4, arrayOfVariantOfDouble4(8), factory2D4
Dim geometricElements4, axis2D4, line2D7, line2D8, point2D6, point2D7, line2D9
Dim constraints4, reference28, reference29, constraint11, length10
Dim reference30, reference31, constraint12, length11, reference32, reference33
Dim constraint13, length12, reference34, reference35, constraint14, length13
Set sketch4 = sketches1.Add(reference3)
arrayOfVariantOfDouble4(0) = 0#
arrayOfVariantOfDouble4(1) = 0#
arrayOfVariantOfDouble4(2) = 0#
arrayOfVariantOfDouble4(3) = 0#
arrayOfVariantOfDouble4(4) = 0#
arrayOfVariantOfDouble4(5) = 0#
arrayOfVariantOfDouble4(6) = 0#
arrayOfVariantOfDouble4(7) = 0#
arrayOfVariantOfDouble4(8) = 0#
Set sketch4Variant = sketch4
sketch4Variant.SetAbsoluteAxisData arrayOfVariantOfDouble4
part1.InWorkObject = sketch4
Set factory2D4 = sketch4.OpenEdition()
Set geometricElements4 = sketch4.GeometricElements
Set axis2D4 = geometricElements4.Item("AbsoluteAxis")
Set line2D7 = axis2D4.GetItem("HDirection")
line2D7.ReportName = 1
Set line2D8 = axis2D4.GetItem("VDirection")
line2D8.ReportName = 2
Set point2D6 = factory2D4.CreatePoint(-Radius1, 0#)
point2D6.ReportName = 3
Set point2D7 = factory2D4.CreatePoint(Radius1, 0#)
point2D7.ReportName = 4
Set line2D9 = factory2D4.CreateLine(-Radius1, 0#, Radius1, 0#)
line2D9.ReportName = 5
line2D9.StartPoint = point2D6
line2D9.EndPoint = point2D7
Set constraints4 = sketch4.Constraints
Set reference28 = part1.CreateReferenceFromObject(point2D6)
Set reference29 = part1.CreateReferenceFromObject(line2D8)
Set constraint11 = constraints4.AddBiEltCst(catCstTypeDistance, reference28, reference29)
constraint11.Mode = catCstModeDrivingDimension
Set length10 = constraint11.Dimension
length10.Value = Radius1
Set reference30 = part1.CreateReferenceFromObject(point2D6)
Set reference31 = part1.CreateReferenceFromObject(line2D7)
Set constraint12 = constraints4.AddBiEltCst(catCstTypeDistance, reference30, reference31)
constraint12.Mode = catCstModeDrivingDimension
Set length11 = constraint12.Dimension
length11.Value = 0#
Set reference32 = part1.CreateReferenceFromObject(point2D7)
Set reference33 = part1.CreateReferenceFromObject(line2D8)
Set constraint13 = constraints4.AddBiEltCst(catCstTypeDistance, reference32, reference33)
constraint13.Mode = catCstModeDrivingDimension
Set length12 = constraint13.Dimension
length12.Value = Radius1
Set reference34 = part1.CreateReferenceFromObject(point2D7)
Set reference35 = part1.CreateReferenceFromObject(line2D7)
Set constraint14 = constraints4.AddBiEltCst(catCstTypeDistance, reference34, reference35)
constraint14.Mode = catCstModeDrivingDimension
Set length13 = constraint14.Dimension
length13.Value = 0#
sketch4.CloseEdition
part1.InWorkObject = sketch4
part1.Update


Dim reference36, groove1, parameters1
Set reference36 = part1.CreateReferenceFromName("")
Set groove1 = shapeFactory1.AddNewGrooveFromRef(reference36)
Set parameters1 = part1.Parameters

' Finding the name of the last groove
Dim FinalGroove
selection1.Search ("Name=Groove*,all")
FinalGroove = selection1.Count2
GrooveName = selection1.Item(FinalGroove).Value.Name


Dim length14, parameters2, length15, reference37
Set length14 = parameters1.Item(Path & "\" & GrooveName & "\ThickThin1")
length14.Value = 1#
Set parameters2 = part1.Parameters
Set length15 = parameters2.Item(Path & "\" & GrooveName & "\ThickThin2")
length15.Value = 0#
Set reference37 = part1.CreateReferenceFromObject(sketch3)
groove1.SetProfileElement reference37

' Finding the name of the last sketch
Dim FinalSketch
selection1.Search ("Name=Sketch*,all")
selectionCountSketch = selection1.Count2
FinalSketch = selectionCountSketch
FinalSketchName = selection1.Item(FinalSketch).Value.Name

Dim reference38
Set reference38 = part1.CreateReferenceFromBRepName("WireREdge:(Wire:(Brp:(" & FinalSketchName & ";5);None:(Limits1:();Limits2:());Cf11:());WithTemporaryBody;WithoutBuildError;WithSelectingFeatureSupport;MFBRepVersion_CXR15)", sketch4)
groove1.RevoluteAxis = reference38
part1.Update

' Hidding the last sketch
HiddingObjects "Sketch", FinalSketchName, bodyName


'---------------------------------------------------------------------------'
Dim sketch5 As Sketch
Set sketch5 = sketches1.Add(reference9)
Dim arrayOfVariantOfDouble5(8)
arrayOfVariantOfDouble5(0) = 0#
arrayOfVariantOfDouble5(1) = 0#
arrayOfVariantOfDouble5(2) = 0#
arrayOfVariantOfDouble5(3) = 0#
arrayOfVariantOfDouble5(4) = 0#
arrayOfVariantOfDouble5(5) = 0#
arrayOfVariantOfDouble5(6) = 0#
arrayOfVariantOfDouble5(7) = 0#
arrayOfVariantOfDouble5(8) = 0#
Set sketch5Variant = sketch5
sketch5Variant.SetAbsoluteAxisData arrayOfVariantOfDouble5
part1.InWorkObject = sketch5
Dim factory2D5 As Factory2D
Set factory2D5 = sketch5.OpenEdition()
Dim geometricElements5 As GeometricElements
Set geometricElements5 = sketch5.GeometricElements
Dim axis2D5 As Axis2D
Set axis2D5 = geometricElements5.Item("AbsoluteAxis")
Dim line2D10 As Line2D
Set line2D10 = axis2D5.GetItem("HDirection")
line2D10.ReportName = 2
Dim line2D11 As Line2D
Set line2D11 = axis2D5.GetItem("VDirection")
line2D11.ReportName = 3
Dim point2D8 As Point2D
Set point2D8 = factory2D5.CreatePoint(0#, 0#)
point2D8.ReportName = 4
Dim point2D9 As Point2D
Set point2D9 = factory2D5.CreatePoint(-Radius2, 0#)
point2D9.ReportName = 5
Dim point2D10 As Point2D
Set point2D10 = factory2D5.CreatePoint(Radius2, 0#)
point2D10.ReportName = 6
Dim circle2D4 As Circle2D
Set circle2D4 = factory2D5.CreateCircle(0#, 0#, Radius2, 3.141593, 6.283185)
circle2D4.CenterPoint = point2D8
circle2D4.ReportName = 7
circle2D4.StartPoint = point2D9
circle2D4.EndPoint = point2D10
Dim constraints5 As Constraints
Set constraints5 = sketch5.Constraints
Dim reference39 As Reference
Set reference39 = part1.CreateReferenceFromObject(point2D8)
Dim reference40 As Reference
Set reference40 = part1.CreateReferenceFromObject(line2D11)
Dim constraint15 As Constraint
Set constraint15 = constraints5.AddBiEltCst(catCstTypeDistance, reference39, reference40)
constraint15.Mode = catCstModeDrivingDimension
Dim length16 As Length
Set length16 = constraint15.Dimension
length16.Value = 0#
Dim reference41 As Reference
Set reference41 = part1.CreateReferenceFromObject(point2D8)
Dim reference42 As Reference
Set reference42 = part1.CreateReferenceFromObject(line2D10)
Dim constraint16 As Constraint
Set constraint16 = constraints5.AddBiEltCst(catCstTypeDistance, reference41, reference42)
constraint16.Mode = catCstModeDrivingDimension
Dim length17 As Length
Set length17 = constraint16.Dimension
length17.Value = 0#
Dim reference43 As Reference
Set reference43 = part1.CreateReferenceFromObject(circle2D4)
Dim constraint17 As Constraint
Set constraint17 = constraints5.AddMonoEltCst(catCstTypeRadius, reference43)
constraint17.Mode = catCstModeDrivingDimension
Dim length18 As Length
Set length18 = constraint17.Dimension
length18.Value = Radius2
Dim reference44 As Reference
Set reference44 = part1.CreateReferenceFromObject(point2D9)
Dim reference45 As Reference
Set reference45 = part1.CreateReferenceFromObject(line2D10)
Dim constraint18 As Constraint
Set constraint18 = constraints5.AddBiEltCst(catCstTypeOn, reference44, reference45)
constraint18.Mode = catCstModeDrivingDimension
sketch5.CloseEdition
part1.InWorkObject = sketch5
part1.Update

Dim sketch6, arrayOfVariantOfDouble6(8), factory2D6
Dim geometricElements6, axis2D6, line2D12, line2D13, point2D11, point2D12
Dim line2D14, constraints6, reference46, reference47, constraint19, length19
Dim reference48, reference49, constraint20, length20, reference50, reference51
Dim constraint21, length21, reference52, reference53, constraint22, length22
Set sketch6 = sketches1.Add(reference9)
arrayOfVariantOfDouble6(0) = 0#
arrayOfVariantOfDouble6(1) = 0#
arrayOfVariantOfDouble6(2) = 0#
arrayOfVariantOfDouble6(3) = 0#
arrayOfVariantOfDouble6(4) = 0#
arrayOfVariantOfDouble6(5) = 0#
arrayOfVariantOfDouble6(6) = 0#
arrayOfVariantOfDouble6(7) = 0#
arrayOfVariantOfDouble6(8) = 0#
Set sketch6Variant = sketch6
sketch6Variant.SetAbsoluteAxisData arrayOfVariantOfDouble6
part1.InWorkObject = sketch6
Set factory2D6 = sketch6.OpenEdition()
Set geometricElements6 = sketch6.GeometricElements
Set axis2D6 = geometricElements6.Item("AbsoluteAxis")
Set line2D12 = axis2D6.GetItem("HDirection")
line2D12.ReportName = 1
Set line2D13 = axis2D6.GetItem("VDirection")
line2D13.ReportName = 2
Set point2D11 = factory2D6.CreatePoint(-Radius2, 0#)
point2D11.ReportName = 3
Set point2D12 = factory2D6.CreatePoint(Radius2, 0#)
point2D12.ReportName = 4
Set line2D14 = factory2D6.CreateLine(-Radius2, 0#, Radius2, 0#)
line2D14.ReportName = 5
line2D14.StartPoint = point2D11
line2D14.EndPoint = point2D12
Set constraints6 = sketch6.Constraints
Set reference46 = part1.CreateReferenceFromObject(point2D11)
Set reference47 = part1.CreateReferenceFromObject(line2D13)
Set constraint19 = constraints6.AddBiEltCst(catCstTypeDistance, reference46, reference47)
constraint19.Mode = catCstModeDrivingDimension
Set length19 = constraint19.Dimension
length19.Value = Radius2
Set reference48 = part1.CreateReferenceFromObject(point2D11)
Set reference49 = part1.CreateReferenceFromObject(line2D12)
Set constraint20 = constraints6.AddBiEltCst(catCstTypeDistance, reference48, reference49)
constraint20.Mode = catCstModeDrivingDimension
Set length20 = constraint20.Dimension
length20.Value = 0#
Set reference50 = part1.CreateReferenceFromObject(point2D12)
Set reference51 = part1.CreateReferenceFromObject(line2D13)
Set constraint21 = constraints6.AddBiEltCst(catCstTypeDistance, reference50, reference51)
constraint21.Mode = catCstModeDrivingDimension
Set length21 = constraint21.Dimension
length21.Value = Radius2
Set reference52 = part1.CreateReferenceFromObject(point2D12)
Set reference53 = part1.CreateReferenceFromObject(line2D12)
Set constraint22 = constraints6.AddBiEltCst(catCstTypeDistance, reference52, reference53)
constraint22.Mode = catCstModeDrivingDimension
Set length22 = constraint22.Dimension
length22.Value = 0#
sketch6.CloseEdition
part1.InWorkObject = sketch6
part1.Update


Dim reference54, groove2, parameters3
Set reference54 = part1.CreateReferenceFromName("")
Set groove2 = shapeFactory1.AddNewGrooveFromRef(reference54)
Set parameters3 = part1.Parameters

' Finding the name of the last groove
Dim NewFinalGroove
selection1.Search ("Name=Groove*,all")
NewFinalGroove = selection1.Count2
NewGrooveName = selection1.Item(NewFinalGroove).Value.Name


Dim length23, parameters4, length24, reference55
Set length23 = parameters3.Item(Path & "\" & NewGrooveName & "\ThickThin1")
length23.Value = 1#
Set parameters4 = part1.Parameters
Set length24 = parameters4.Item(Path & "\" & NewGrooveName & "\ThickThin2")
length24.Value = 0#
Set reference55 = part1.CreateReferenceFromObject(sketch5)
groove2.SetProfileElement reference55

' Finding the name of the last sketch
Dim NewFinalSketch
selection1.Search ("Name=Sketch*,all")
NewselectionCountSketch = selection1.Count2
NewFinalSketch = NewselectionCountSketch
NewFinalSketchName = selection1.Item(NewFinalSketch).Value.Name

Dim reference56
Set reference56 = part1.CreateReferenceFromBRepName("WireREdge:(Wire:(Brp:(" & NewFinalSketchName & ";5);None:(Limits1:();Limits2:());Cf11:());WithTemporaryBody;WithoutBuildError;WithSelectingFeatureSupport;MFBRepVersion_CXR15)", sketch6)
groove2.RevoluteAxis = reference56
part1.Update

' Hidding the last sketch
HiddingObjects "Sketch", NewFinalSketchName, bodyName

End Sub

' Hidding an object that is of a specific type
Sub HiddingObjects(TypeOfObject As String, ObjectName, bodyName)

Dim partDocument1, selection1, visPropertySet1, part1, bodies1, body1
Set partDocument1 = CATIA.ActiveDocument

Set selection1 = partDocument1.Selection

Set visPropertySet1 = selection1.VisProperties

Set part1 = partDocument1.Part

Set bodies1 = part1.Bodies

Set body1 = bodies1.Item(bodyName)

If TypeOfObject = "Plane" Then

    Dim hybridShapes1, hybridShapePlaneEquation1, bSTRING1
    Set hybridShapes1 = body1.HybridShapes
    
    Set hybridShapePlaneEquation1 = hybridShapes1.Item(ObjectName) ' Plane name
    
    Set hybridShapes1 = hybridShapePlaneEquation1.Parent
    
    bSTRING1 = hybridShapePlaneEquation1.Name
    
    selection1.Add hybridShapePlaneEquation1

ElseIf TypeOfObject = "Sketch" Then
    
    Dim sketches1, sketch1, bSTRING2
    Set sketches1 = body1.Sketches
    
    Set sketch1 = sketches1.Item(ObjectName) ' Sketch name
    
    Set sketches1 = sketch1.Parent
    
    bSTRING2 = sketch1.Name
    
    selection1.Add sketch1
    
ElseIf TypeOfObject = "Extremum" Then
    
    Dim hybridShapes2, hybridShapeExtremum1, bSTRING3
    Set hybridShapes2 = body1.HybridShapes
    
    Set hybridShapeExtremum1 = hybridShapes2.Item(ObjectName) ' Extremum name
    
    Set hybridShapes2 = hybridShapeExtremum1.Parent
    
    bSTRING3 = hybridShapeExtremum1.Name
    
    selection1.Add hybridShapeExtremum1

ElseIf TypeOfObject = "Point" Then
    
    Dim hybridShapes3, hybridShapePointCoord1, bSTRING4
    Set hybridShapes3 = body1.HybridShapes
    
    Set hybridShapePointCoord1 = hybridShapes3.Item(ObjectName) ' Point name
    
    Set hybridShapes3 = hybridShapePointCoord1.Parent
    
    bSTRING4 = hybridShapePointCoord1.Name
    
    selection1.Add hybridShapePointCoord1

End If

Set visPropertySet1 = visPropertySet1.Parent

Dim bSTR2, bSTR3
bSTR2 = visPropertySet1.Name

bSTR3 = visPropertySet1.Name

visPropertySet1.SetShow 1

selection1.Clear

End Sub

Attribute VB_Name = "TableGeneration"
Sub CATMain()


' check if part is active
On Error Resume Next
'If CATIA.ActiveDocument.Name <> "" Then 'exists Then
    Dim Document
    Set Document = CATIA.ActiveDocument
    MyErrNumber = Err.Number
    On Error GoTo 0   ' Reset error handling
If MyErrNumber <> 0 Then
'Else
    Dim strFilePathPart, documents1, document1, specsAndGeomWindow1, viewer3D1, viewpoint3D1

    'Display file open dialog
    strFilePathPart = CATIA.FileSelectionBox("Select Part File", "*.*", 0)
    'If user clicked cancel (empty string is returned), then exit the program
    If strFilePathPart = "" Then ' if no part has been selected
        MsgBox "No part has been selected! Please open a part or select one."
        Exit Sub
    Else
        Set documents1 = CATIA.Documents
        Set document1 = documents1.Open(strFilePathPart)
        Set specsAndGeomWindow1 = CATIA.ActiveWindow
        Set viewer3D1 = specsAndGeomWindow1.ActiveViewer
        viewer3D1.Reframe
        Set viewpoint3D1 = viewer3D1.Viewpoint3D
    End If
End If


' Path of current part
Dim partPath
partPath = CATIA.ActiveDocument.Path



Dim StrFilePath As String
Dim objFile As File
Dim objTextStream As TextStream
Dim strLine As String
 
'Display file open dialog
StrFilePath = CATIA.FileSelectionBox("Select DataSet File", "*.csv; *.xl??", 0)
'check excelfile provided
'If user clicked cancel (empty string is returned), then exit the program
If StrFilePath <> "" Then
    
   Set ofName = CATIA.FileSystem.GetFile(StrFilePath)
   
   Dim tStream As TextStream
   Dim strText As String

   Set tStream = ofName.OpenAsTextStream("ForReading")                'open the text stream
   Dim rows
   rows = 0
   Do
      strText = tStream.ReadLine                                     'read the file one line at a time
      If strText = "" Then
      Exit Do
      End If
      rows = rows + 1
   Loop
   tStream.Close
   
    
    Set excelApp = GetObject(StrFilePath)
Else ' generate a new table that needs to be populated

    Dim ExcelSheet As Object
    Set ExcelSheet = CreateObject("Excel.Sheet")

    
    ' Make Excel visible through the Application object.
    'ExcelSheet.Application.Visible = True
    ' Place some text in the first cell of the sheet.
    ExcelSheet.Application.Cells(1, 1).Value = "X"
    ExcelSheet.Application.Cells(1, 2).Value = "Y"
    ExcelSheet.Application.Cells(1, 3).Value = "Z"
    ExcelSheet.Application.Cells(1, 4).Value = "Radius"
    ' Save the sheet
    ExcelSheet.SaveAs partPath & "/DataSheet.csv"
    ' Close Excel with the Quit method on the Application object.
    'ExcelSheet.Application.Quit
    ' Release the object variable.
    Set ExcelSheet = Nothing

    MsgBox "Please populate the DataSheet.csv table and run the macro again."
    Exit Sub
End If


Dim X1 As Integer, Y1 As Integer, Z1 As Integer, R1 As Integer, X2 As Integer, Y2 As Integer, Z2 As Integer, R2 As Integer
For ii = 3 To rows
    jj = ii - 1
    X1 = excelApp.Application.Range("A" & jj)
    Y1 = excelApp.Application.Range("B" & jj)
    Z1 = excelApp.Application.Range("C" & jj)
    R1 = excelApp.Application.Range("D" & jj)
    X2 = excelApp.Application.Range("A" & ii)
    Y2 = excelApp.Application.Range("B" & ii)
    Z2 = excelApp.Application.Range("C" & ii)
    R2 = excelApp.Application.Range("D" & ii)

    ChannelGenerator.CATMain X1, Y1, Z1, R1, X2, Y2, Z2, R2
    On Error Resume Next

Next


End Sub
