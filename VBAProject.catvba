Attribute VB_Name = "GrooveSphericalCut3"
Const Plane1 = "Plane.35"
Const XPoint = 40
Const YPoint = 40
Const Radius = 5

Sub CATMain()

Dim partDocument1 As PartDocument
Set partDocument1 = CATIA.ActiveDocument

Dim part1 As Part
Set part1 = partDocument1.Part

Dim bodies1 As Bodies
Set bodies1 = part1.Bodies

Dim body1 As Body
Set body1 = bodies1.Item("PartBody")

Dim sketches1 As Sketches
Set sketches1 = body1.Sketches

Dim hybridShapes1 As HybridShapes
Set hybridShapes1 = body1.HybridShapes

Dim reference1 As Reference
Set reference1 = hybridShapes1.Item(Plane1)

Dim sketch1 As Sketch
Set sketch1 = sketches1.Add(reference1)

Dim arrayOfVariantOfDouble1(8)
arrayOfVariantOfDouble1(0) = 0#
arrayOfVariantOfDouble1(1) = -40#
arrayOfVariantOfDouble1(2) = -0#
arrayOfVariantOfDouble1(3) = -1#
arrayOfVariantOfDouble1(4) = 0#
arrayOfVariantOfDouble1(5) = -0#
arrayOfVariantOfDouble1(6) = -0#
arrayOfVariantOfDouble1(7) = 0#
arrayOfVariantOfDouble1(8) = 1#
Set sketch1Variant = sketch1
sketch1Variant.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As Axis2D
Set axis2D1 = geometricElements1.Item("AbsoluteAxis")

Dim line2D1 As Line2D
Set line2D1 = axis2D1.GetItem("HDirection")

line2D1.ReportName = 2

Dim line2D2 As Line2D
Set line2D2 = axis2D1.GetItem("VDirection")

line2D2.ReportName = 3

Dim point2D1 As Point2D
Set point2D1 = factory2D1.CreatePoint(XPoint, YPoint)

point2D1.ReportName = 4

Dim point2D2 As Point2D
Set point2D2 = factory2D1.CreatePoint(XPoint - Radius, YPoint)

point2D2.ReportName = 5

Dim point2D3 As Point2D
Set point2D3 = factory2D1.CreatePoint(XPoint + Radius, YPoint)

point2D3.ReportName = 6

Dim circle2D1 As Circle2D
Set circle2D1 = factory2D1.CreateCircle(XPoint, YPoint, Radius, 3.141593, 6.283185)

circle2D1.CenterPoint = point2D1

circle2D1.ReportName = 7

circle2D1.StartPoint = point2D2

circle2D1.EndPoint = point2D3

Dim line2D3 As Line2D
Set line2D3 = factory2D1.CreateLine(XPoint - Radius, YPoint, XPoint + Radius, YPoint)

line2D3.ReportName = 8

line2D3.StartPoint = point2D2

line2D3.EndPoint = point2D3

Dim constraints1 As Constraints
Set constraints1 = sketch1.Constraints

Dim reference2 As Reference
Set reference2 = part1.CreateReferenceFromObject(point2D1)

Dim reference3 As Reference
Set reference3 = part1.CreateReferenceFromObject(line2D2)

Dim constraint1 As Constraint
Set constraint1 = constraints1.AddBiEltCst(catCstTypeDistance, reference2, reference3)

constraint1.Mode = catCstModeDrivingDimension

Dim length1 As Length
Set length1 = constraint1.Dimension

length1.Value = XPoint

Dim reference4 As Reference
Set reference4 = part1.CreateReferenceFromObject(point2D1)

Dim reference5 As Reference
Set reference5 = part1.CreateReferenceFromObject(line2D1)

Dim constraint2 As Constraint
Set constraint2 = constraints1.AddBiEltCst(catCstTypeDistance, reference4, reference5)

constraint2.Mode = catCstModeDrivingDimension

Dim length2 As Length
Set length2 = constraint2.Dimension

length2.Value = YPoint

Dim reference6 As Reference
Set reference6 = part1.CreateReferenceFromObject(circle2D1)

Dim constraint3 As Constraint
Set constraint3 = constraints1.AddMonoEltCst(catCstTypeRadius, reference6)

constraint3.Mode = catCstModeDrivingDimension

Dim length3 As Length
Set length3 = constraint3.Dimension

length3.Value = Radius

Dim reference7 As Reference
Set reference7 = part1.CreateReferenceFromObject(line2D3)

Dim reference8 As Reference
Set reference8 = part1.CreateReferenceFromObject(line2D1)

Dim constraint4 As Constraint
Set constraint4 = constraints1.AddBiEltCst(catCstTypeHorizontality, reference7, reference8)

constraint4.Mode = catCstModeDrivingDimension

sketch1.CloseEdition

part1.InWorkObject = sketch1

part1.Update

Dim shapeFactory1 As ShapeFactory
Set shapeFactory1 = part1.ShapeFactory

Dim groove1 As Groove
Set groove1 = shapeFactory1.AddNewGroove(sketch1)

Dim parameters1 As Parameters
Set parameters1 = part1.Parameters

' Finding the Groove
Dim selection1 As Selection
Set selection1 = partDocument1.Selection
selection1.Search ("Name=Groove*,all")
selectionCount = selection1.Count2
'MsgBox selectionCount
GrooveName = selection1.Item(selectionCount).Value.Name
'MsgBox GrooveName

Dim length4 As Length
Set length4 = parameters1.Item("Part1\PartBody\" & GrooveName & "\ThickThin1")

length4.Value = 1#

Dim parameters2 As Parameters
Set parameters2 = part1.Parameters

Dim length5 As Length
Set length5 = parameters2.Item("Part1\PartBody\" & GrooveName & "\ThickThin2")

length5.Value = 0#

Dim reference9 As Reference
Set reference9 = part1.CreateReferenceFromBRepName("WireREdge:(Wire:(Brp:(" & Plane1 & ";8);None:(Limits1:();Limits2:());Cf11:());WithTemporaryBody;WithoutBuildError;WithSelectingFeatureSupport;MFBRepVersion_CXR15)", sketch1)

'Dim RevoluteAxis As Reference
'Set RevoluteAxis = reference7

'groove1.RevoluteAxis = reference9
'groove1.RevoluteAxis = reference7
groove1.RevoluteAxis = part1.CreateReferenceFromName("Sketch.46\Edge.22")

'reference object - line2D3

part1.Update

End Sub

Attribute VB_Name = "Module2"
'Const X1 = 12
'Const Y1 = -8
'Const Z1 = 7
'Const X2 = 16
'Const Y2 = 9
'Const Z2 = 2

Const X1 = -40
Const Y1 = -40
Const Z1 = -40
Const X2 = -50
Const Y2 = -50
Const Z2 = -50


'Const A1 = 4
'Const B1 = 17
'Const C1 = -5
'Const D1 = -123
'Const A2 = -4
'Const B2 = -17
'Const C2 = 5
'Const D2 = -207
Const Radius1 = 5
Const Radius2 = 5

'Sub CATMain(Plane2 As String, Plane1 As String, A1 As Integer, B1 As Integer, C1 As Integer, D1 As Integer, A2 As Integer, B2 As Integer, C2 As Integer, D2 As Integer, Radius1 As Integer, Radius2 As Integer)
'Sub CATMain(X1 As Integer, Y1 As Integer, Z1 As Integer, Radius1 As Integer, X2 As Integer, Y2 As Integer, Z2 As Integer, Radius2 As Integer)
Sub CATMain()

Dim A1 As Integer
Dim B1 As Integer
Dim C1 As Integer
Dim D1 As Integer

A1 = X2 - X1
B1 = Y2 - Y1
C1 = Z2 - Z1
D1 = (A1 * X1 + B1 * Y1 + C1 * Z1)
'MsgBox (A1)
'MsgBox (B1)
'MsgBox (C1)
'MsgBox (D1)


Dim A2 As Integer
Dim B2 As Integer
Dim C2 As Integer
Dim D2 As Integer

A2 = X1 - X2
B2 = Y1 - Y2
C2 = Z1 - Z2
D2 = (A2 * X2 + B2 * Y2 + C2 * Z2)
'MsgBox (A2)
'MsgBox (B2)
'MsgBox (C2)
'MsgBox (D2)


Dim partDocument1 As PartDocument
Set partDocument1 = CATIA.ActiveDocument

Dim part1 As Part
Set part1 = partDocument1.Part

Dim hybridShapeFactory1 As HybridShapeFactory
Set hybridShapeFactory1 = part1.HybridShapeFactory

Dim hybridShapePlaneEquation1 As HybridShapePlaneEquation
Set hybridShapePlaneEquation1 = hybridShapeFactory1.AddNewPlaneEquation(A1, B1, C1, D1)

Dim bodies1 As Bodies
Set bodies1 = part1.Bodies

Dim body1 As Body
Set body1 = bodies1.Item("PartBody")

body1.InsertHybridShape hybridShapePlaneEquation1

part1.InWorkObject = hybridShapePlaneEquation1

part1.Update

Dim hybridShapePlaneEquation2 As HybridShapePlaneEquation
Set hybridShapePlaneEquation2 = hybridShapeFactory1.AddNewPlaneEquation(A2, B2, C2, D2)

body1.InsertHybridShape hybridShapePlaneEquation2

part1.InWorkObject = hybridShapePlaneEquation2

part1.Update

Dim selection1 As Selection
Set selection1 = partDocument1.Selection

Dim FirstPlane As Integer
Dim SecondPlane As Integer

selection1.Search ("Name=plane*,all")
selectionCount = selection1.Count2
'MsgBox selectionCount
FirstPlane = selectionCount - 1
SecondPlane = selectionCount
FirstPlaneName = selection1.Item(FirstPlane).Value.Name
'MsgBox FirstPlaneName
SecondPlaneName = selection1.Item(SecondPlane).Value.Name
'MsgBox SecondPlaneName

Dim sketches1 As Sketches
Set sketches1 = body1.Sketches

Dim hybridShapes1 As HybridShapes
Set hybridShapes1 = body1.HybridShapes

Dim reference1 As Reference
Set reference1 = hybridShapes1.Item(SecondPlaneName)

Dim sketch1 As Sketch
Set sketch1 = sketches1.Add(reference1)

Dim arrayOfVariantOfDouble1(8)
arrayOfVariantOfDouble1(0) = 0#
arrayOfVariantOfDouble1(1) = 0#
arrayOfVariantOfDouble1(2) = 0#
arrayOfVariantOfDouble1(3) = 0#
arrayOfVariantOfDouble1(4) = 0#
arrayOfVariantOfDouble1(5) = 0#
arrayOfVariantOfDouble1(6) = 0#
arrayOfVariantOfDouble1(7) = 0#
arrayOfVariantOfDouble1(8) = 0#

'Dim arrayOfVariantOfDouble1(8)
'arrayOfVariantOfDouble1(0) = 2.509091
'arrayOfVariantOfDouble1(1) = 10.663636
'arrayOfVariantOfDouble1(2) = -3.136364
'arrayOfVariantOfDouble1(3) = 0.973417
'arrayOfVariantOfDouble1(4) = -0.229039
'arrayOfVariantOfDouble1(5) = -0#
'arrayOfVariantOfDouble1(6) = 0.063041
'arrayOfVariantOfDouble1(7) = 0.267924
'arrayOfVariantOfDouble1(8) = 0.961375
Set sketch1Variant = sketch1
sketch1Variant.SetAbsoluteAxisData arrayOfVariantOfDouble1

part1.InWorkObject = sketch1

Dim factory2D1 As Factory2D
Set factory2D1 = sketch1.OpenEdition()

Dim geometricElements1 As GeometricElements
Set geometricElements1 = sketch1.GeometricElements

Dim axis2D1 As Axis2D
Set axis2D1 = geometricElements1.Item("AbsoluteAxis")

Dim line2D1 As Line2D
Set line2D1 = axis2D1.GetItem("HDirection")

line2D1.ReportName = 1

Dim line2D2 As Line2D
Set line2D2 = axis2D1.GetItem("VDirection")

line2D2.ReportName = 2

Dim point2D1 As Point2D
Set point2D1 = factory2D1.CreatePoint(0#, 0#)

point2D1.ReportName = 3

Dim circle2D1 As Circle2D
Set circle2D1 = factory2D1.CreateClosedCircle(0#, 0#, Radius2)

circle2D1.CenterPoint = point2D1

circle2D1.ReportName = 4

Dim constraints1 As Constraints
Set constraints1 = sketch1.Constraints

Dim reference2 As Reference
Set reference2 = part1.CreateReferenceFromObject(point2D1)

Dim reference3 As Reference
Set reference3 = part1.CreateReferenceFromObject(line2D2)

Dim constraint1 As Constraint
Set constraint1 = constraints1.AddBiEltCst(catCstTypeDistance, reference2, reference3)

constraint1.Mode = catCstModeDrivingDimension

Dim length1 As Length
Set length1 = constraint1.Dimension

length1.Value = 0#

Dim reference4 As Reference
Set reference4 = part1.CreateReferenceFromObject(point2D1)

Dim reference5 As Reference
Set reference5 = part1.CreateReferenceFromObject(line2D1)

Dim constraint2 As Constraint
Set constraint2 = constraints1.AddBiEltCst(catCstTypeDistance, reference4, reference5)

constraint2.Mode = catCstModeDrivingDimension

Dim length2 As Length
Set length2 = constraint2.Dimension

length2.Value = 0#

Dim reference6 As Reference
Set reference6 = part1.CreateReferenceFromObject(circle2D1)

Dim constraint3 As Constraint
Set constraint3 = constraints1.AddMonoEltCst(catCstTypeRadius, reference6)

constraint3.Mode = catCstModeDrivingDimension

Dim length3 As Length
Set length3 = constraint3.Dimension

length3.Value = Radius2

sketch1.CloseEdition

part1.InWorkObject = sketch1

part1.Update

Dim reference7 As Reference
Set reference7 = hybridShapes1.Item(FirstPlaneName)

Dim sketch2 As Sketch
Set sketch2 = sketches1.Add(reference7)

Dim arrayOfVariantOfDouble2(8)
arrayOfVariantOfDouble2(0) = 0#
arrayOfVariantOfDouble2(1) = 0#
arrayOfVariantOfDouble2(2) = 0#
arrayOfVariantOfDouble2(3) = 0#
arrayOfVariantOfDouble2(4) = 0#
arrayOfVariantOfDouble2(5) = 0#
arrayOfVariantOfDouble2(6) = 0#
arrayOfVariantOfDouble2(7) = 0#
arrayOfVariantOfDouble2(8) = 0#

'Dim arrayOfVariantOfDouble2(8)
'arrayOfVariantOfDouble2(0) = -1.490909
'arrayOfVariantOfDouble2(1) = -6.336364
'arrayOfVariantOfDouble2(2) = 1.863636
'arrayOfVariantOfDouble2(3) = -0.973417
'arrayOfVariantOfDouble2(4) = 0.229039
'arrayOfVariantOfDouble2(5) = 0#
'arrayOfVariantOfDouble2(6) = 0.063041
'arrayOfVariantOfDouble2(7) = 0.267924
'arrayOfVariantOfDouble2(8) = 0.961375
Set sketch2Variant = sketch2
sketch2Variant.SetAbsoluteAxisData arrayOfVariantOfDouble2

part1.InWorkObject = sketch2

Dim factory2D2 As Factory2D
Set factory2D2 = sketch2.OpenEdition()

Dim geometricElements2 As GeometricElements
Set geometricElements2 = sketch2.GeometricElements

Dim axis2D2 As Axis2D
Set axis2D2 = geometricElements2.Item("AbsoluteAxis")

Dim line2D3 As Line2D
Set line2D3 = axis2D2.GetItem("HDirection")

line2D3.ReportName = 1

Dim line2D4 As Line2D
Set line2D4 = axis2D2.GetItem("VDirection")

line2D4.ReportName = 2

Dim point2D2 As Point2D
Set point2D2 = factory2D2.CreatePoint(0#, 0#)

point2D2.ReportName = 3

Dim circle2D2 As Circle2D
Set circle2D2 = factory2D2.CreateClosedCircle(0#, 0#, Radius1)

circle2D2.CenterPoint = point2D2

circle2D2.ReportName = 4

Dim constraints2 As Constraints
Set constraints2 = sketch2.Constraints

Dim reference8 As Reference
Set reference8 = part1.CreateReferenceFromObject(point2D2)

Dim reference9 As Reference
Set reference9 = part1.CreateReferenceFromObject(line2D4)

Dim constraint4 As Constraint
Set constraint4 = constraints2.AddBiEltCst(catCstTypeDistance, reference8, reference9)

constraint4.Mode = catCstModeDrivingDimension

Dim length4 As Length
Set length4 = constraint4.Dimension

length4.Value = 0#

Dim reference10 As Reference
Set reference10 = part1.CreateReferenceFromObject(point2D2)

Dim reference11 As Reference
Set reference11 = part1.CreateReferenceFromObject(line2D3)

Dim constraint5 As Constraint
Set constraint5 = constraints2.AddBiEltCst(catCstTypeDistance, reference10, reference11)

constraint5.Mode = catCstModeDrivingDimension

Dim length5 As Length
Set length5 = constraint5.Dimension

length5.Value = 0#

Dim reference12 As Reference
Set reference12 = part1.CreateReferenceFromObject(circle2D2)

Dim constraint6 As Constraint
Set constraint6 = constraints2.AddMonoEltCst(catCstTypeRadius, reference12)

constraint6.Mode = catCstModeDrivingDimension

Dim length6 As Length
Set length6 = constraint6.Dimension

length6.Value = Radius1

sketch2.CloseEdition

part1.InWorkObject = sketch2

part1.Update

Dim hybridShapeDirection1 As HybridShapeDirection
Set hybridShapeDirection1 = hybridShapeFactory1.AddNewDirectionByCoord(1#, 2#, 3#)

Dim reference13 As Reference
Set reference13 = part1.CreateReferenceFromObject(sketch2)

Dim hybridShapeExtremum1 As HybridShapeExtremum
Set hybridShapeExtremum1 = hybridShapeFactory1.AddNewExtremum(reference13, hybridShapeDirection1, 1)

body1.InsertHybridShape hybridShapeExtremum1

part1.InWorkObject = hybridShapeExtremum1

part1.Update

Dim hybridShapeDirection2 As HybridShapeDirection
Set hybridShapeDirection2 = hybridShapeFactory1.AddNewDirectionByCoord(1#, 2#, 3#)

Dim reference14 As Reference
Set reference14 = part1.CreateReferenceFromObject(sketch1)

Dim hybridShapeExtremum2 As HybridShapeExtremum
Set hybridShapeExtremum2 = hybridShapeFactory1.AddNewExtremum(reference14, hybridShapeDirection2, 1)

body1.InsertHybridShape hybridShapeExtremum2

part1.InWorkObject = hybridShapeExtremum2

part1.Update

Dim shapeFactory1 As ShapeFactory
Set shapeFactory1 = part1.ShapeFactory

Dim loft1 As Loft
Set loft1 = shapeFactory1.AddNewRemovedLoft()

Dim hybridShapeLoft1 As HybridShapeLoft
Set hybridShapeLoft1 = loft1.HybridShape

hybridShapeLoft1.SectionCoupling = 3

hybridShapeLoft1.Relimitation = 1

hybridShapeLoft1.CanonicalDetection = 2

Dim reference15 As Reference
Set reference15 = part1.CreateReferenceFromObject(sketch2)

Dim reference16 As Reference
Set reference16 = part1.CreateReferenceFromObject(hybridShapeExtremum1)

hybridShapeLoft1.AddSectionToLoft reference15, 1, reference16

Dim reference17 As Reference
Set reference17 = part1.CreateReferenceFromObject(sketch1)

Dim reference18 As Reference
Set reference18 = part1.CreateReferenceFromObject(hybridShapeExtremum2)

hybridShapeLoft1.AddSectionToLoft reference17, -1, reference18

part1.InWorkObject = hybridShapeLoft1

part1.Update



HiddingObjects "Plane", FirstPlaneName
HiddingObjects "Plane", SecondPlaneName

' Hidding the 2 created sketches
Dim FirstSketch As Integer
Dim SecondSketch As Integer
selection1.Search ("Name=Sketch*,all")
selectionCount = selection1.Count2
'MsgBox selectionCount
FirstSketch = selectionCount - 1
SecondSketch = selectionCount
FirstSketchName = selection1.Item(FirstSketch).Value.Name
'MsgBox FirstSketchName
SecondSketchName = selection1.Item(SecondSketch).Value.Name
'MsgBox SecondSketchName

HiddingObjects "Sketch", FirstSketchName
HiddingObjects "Sketch", SecondSketchName


' Hidding the 2 created extremum
Dim FirstExtremum As Integer
Dim SecondExtremum As Integer
selection1.Search ("Name=Extremum*,all")
selectionCount = selection1.Count2
'MsgBox selectionCount
FirstExtremum = selectionCount - 1
SecondExtremum = selectionCount
FirstExtremumName = selection1.Item(FirstExtremum).Value.Name
'MsgBox FirstSketchName
SecondExtremumName = selection1.Item(SecondExtremum).Value.Name
'MsgBox SecondSketchName

HiddingObjects "Extremum", FirstExtremumName
HiddingObjects "Extremum", SecondExtremumName

End Sub

' Hidding an object that is of a specific type
Sub HiddingObjects(TypeOfObject As String, ObjectName)

Dim partDocument1 As PartDocument
Set partDocument1 = CATIA.ActiveDocument

Dim selection1 As Selection
Set selection1 = partDocument1.Selection

Dim visPropertySet1 As VisPropertySet
Set visPropertySet1 = selection1.VisProperties

Dim part1 As Part
Set part1 = partDocument1.Part

Dim bodies1 As Bodies
Set bodies1 = part1.Bodies

Dim body1 As Body
Set body1 = bodies1.Item("PartBody")

If TypeOfObject = "Plane" Then

    Dim hybridShapes1 As HybridShapes
    Set hybridShapes1 = body1.HybridShapes
    
    Dim hybridShapePlaneEquation1 As HybridShapePlaneEquation
    Set hybridShapePlaneEquation1 = hybridShapes1.Item(ObjectName) ' Plane name
    
    Set hybridShapes1 = hybridShapePlaneEquation1.Parent
    
    Dim bSTRING1 As String
    bSTRING1 = hybridShapePlaneEquation1.Name
    
    selection1.Add hybridShapePlaneEquation1

ElseIf TypeOfObject = "Sketch" Then
    
    Dim sketches1 As Sketches
    Set sketches1 = body1.Sketches
    
    Dim sketch1 As Sketch
    Set sketch1 = sketches1.Item(ObjectName) ' Sketch name
    
    Set sketches1 = sketch1.Parent
    
    Dim bSTRING2 As String
    bSTRING2 = sketch1.Name
    
    selection1.Add sketch1
    
ElseIf TypeOfObject = "Extremum" Then
    
    Dim hybridShapes2 As HybridShapes
    Set hybridShapes2 = body1.HybridShapes
    
    Dim hybridShapeExtremum1 As HybridShapeExtremum
    Set hybridShapeExtremum1 = hybridShapes2.Item(ObjectName) ' Extremum name
    
    Set hybridShapes2 = hybridShapeExtremum1.Parent
    
    Dim bSTRING3 As String
    bSTRING3 = hybridShapeExtremum1.Name
    
    selection1.Add hybridShapeExtremum1

End If

Set visPropertySet1 = visPropertySet1.Parent

Dim bSTR2 As String
bSTR2 = visPropertySet1.Name

Dim bSTR3 As String
bSTR3 = visPropertySet1.Name

visPropertySet1.SetShow 1

selection1.Clear

End Sub

Attribute VB_Name = "SummeryOfProject"

Sub CATMain()

' Get points from datasheet

' Add if statement for every entry inside the data sheet

ResponseX1 = CInt(InputBox("X1"))
ResponseY1 = CInt(InputBox("Y1"))
ResponseZ1 = CInt(InputBox("Z1"))
ResponseX2 = CInt(InputBox("X2"))
ResponseY2 = CInt(InputBox("Y2"))
ResponseZ2 = CInt(InputBox("Z2"))


'Sub CATMain2(InitialPointX As Integer, InitialPointY As Integer, InitialPointZ As Integer, FinalPointX As Integer, FinalPointY As Integer, FinalPointZ As Integer)

' Point Allocation
Dim StartPointX As Integer
StartPointX = ResponseX1 'InitialPointX

Dim StartPointY As Integer
StartPointY = ResponseY1 'InitialPointY

Dim StartPointZ As Integer
StartPointZ = ResponseZ1 'InitialPointZ

Dim EndPointX As Integer
EndPointX = ResponseX2 ' FinalPointX

Dim EndPointY As Integer
EndPointY = ResponseY2 ' FinalPointY

Dim EndPointZ As Integer
EndPointZ = ResponseZ2 ' FinalPointZ

Dim PerpendicularPlaneVectorX As Integer
PerpendicularPlaneVectorX = EndPointX - StartPointX

Dim PerpendicularPlaneVectorY As Integer
PerpendicularPlaneVectorY = EndPointY - StartPointY

Dim PerpendicularPlaneVectorZ As Integer
PerpendicularPlaneVectorZ = EndPointZ - StartPointZ

Dim RemainderOfEquation As Integer
RemainderOfEquation = (PerpendicularPlaneVectorX * StartPointX + PerpendicularPlaneVectorY * StartPointY + PerpendicularPlaneVectorZ * StartPointZ)

MsgBox (PerpendicularPlaneVectorX)
MsgBox (PerpendicularPlaneVectorY)
MsgBox (PerpendicularPlaneVectorZ)
MsgBox (RemainderOfEquation)
'' Generate a plane for the start point
PlaneGenerationUsingPlaneEquation PerpendicularPlaneVectorX, PerpendicularPlaneVectorY, PerpendicularPlaneVectorZ, RemainderOfEquation

' Point Allocation
'Dim StartPointX As Integer
StartPointX = ResponseX1 'InitialPointX

'Dim StartPointY As Integer
StartPointY = ResponseY1 'InitialPointY

'Dim StartPointZ As Integer
StartPointZ = ResponseZ1 'InitialPointZ

'Dim EndPointX As Integer
EndPointX = ResponseX2 ' FinalPointX

'Dim EndPointY As Integer
EndPointY = ResponseY2 ' FinalPointY

'Dim EndPointZ As Integer
EndPointZ = ResponseZ2 ' FinalPointZ

'Dim PerpendicularPlaneVectorX As Integer
PerpendicularPlaneVectorX = StartPointX - EndPointX

'Dim PerpendicularPlaneVectorY As Integer
PerpendicularPlaneVectorY = StartPointY - EndPointY

'Dim PerpendicularPlaneVectorZ As Integer
PerpendicularPlaneVectorZ = StartPointZ - EndPointZ

'Dim RemainderOfEquation As Integer
RemainderOfEquation = (PerpendicularPlaneVectorX * EndPointX + PerpendicularPlaneVectorY * EndPointY + PerpendicularPlaneVectorZ * EndPointZ)

MsgBox (PerpendicularPlaneVectorX)
MsgBox (PerpendicularPlaneVectorY)
MsgBox (PerpendicularPlaneVectorZ)
MsgBox (RemainderOfEquation)
'' Generate a plane for the end point
PlaneGenerationUsingPlaneEquation PerpendicularPlaneVectorX, PerpendicularPlaneVectorY, PerpendicularPlaneVectorZ, RemainderOfEquation

End Sub


'' Plane Generation Using Plane Equation
'Sub PlaneGenerationUsingPlaneEquation(A As Integer, B As Integer, C As Integer, D As Integer)
'
'Dim partDocument1 As PartDocument
'Set partDocument1 = CATIA.ActiveDocument
'
'Dim part1 As Part
'Set part1 = partDocument1.Part
'
'Dim hybridShapeFactory1 As HybridShapeFactory
'Set hybridShapeFactory1 = part1.HybridShapeFactory
'
'Dim hybridShapePlaneEquation1 As HybridShapePlaneEquation
'Set hybridShapePlaneEquation1 = hybridShapeFactory1.AddNewPlaneEquation(A, B, C, D)
'
'Dim bodies1 As Bodies
'Set bodies1 = part1.Bodies
'
'Dim body1 As Body
'Set body1 = bodies1.Item("PartBody")
'
'body1.InsertHybridShape hybridShapePlaneEquation1
'
'part1.InWorkObject = hybridShapePlaneEquation1
'
'part1.Update
'
'End Sub

Attribute VB_Name = "TableGeneration"
Sub CATMain()

Dim partDocument1 As PartDocument
Set partDocument1 = CATIA.ActiveDocument

Dim part1 As Part
Set part1 = partDocument1.Part

Dim relations1 As Relations
Set relations1 = part1.Relations

Dim designTable1 As DesignTable
Set designTable1 = relations1.CreateDesignTable("DesignTable.1", "DesignTable created by pasho 3/14/2020", False, "C:\Users\pasho\Desktop\CatiaScripts\DesignTable1.xlsx")

End Sub
