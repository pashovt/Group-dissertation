Attribute VB_Name = "modPointsFromCSV"
'---------------------------------------------------------------------------------------
' Module    : modSetPointsFromCVSFile
' DateTime  : 15.10.2006 03:42
' Author    : Joseph Herzog
' Purpose   : sets points read from a CSV - file into a new catpart and
'             saves the part to the CSV-file's name.
'---------------------------------------------------------------------------------------
'Anwendung: Datei mit den Punktdaten und der Endung '.CSV' auswählen. Es werden dann die Punkte
'           generiert und in einem CATPart abgespeichert.
'Das erwartete Datenformat: Je Zeile der Name des Punktes sowie seine XYZ-Koordinaten, durch
'           Komma oder Strichpunkt getrennt.
'Beispiel: P000;1162,37819194794;5982,28096961975;4944,81384754181
'          P001;2165,49158096313;5053,62927913666;2113,70348930359
'          P002;5635,0189447403;5341,45832061768;2285,98296642303
'          P003;2635,88070869446;9910,77244281769;7487,3423576355
'oder
'          P000,1162.37819194794,5982.28096961975,4944.81384754181
'          P001,2165.49158096313,5053.62927913666,2113.70348930359
'          P002,5635.0189447403,5341.45832061768,2285.98296642303
'          P003,2635.88070869446,9910.77244281769,7487.3423576355
'
'Nicht zulässige Zeichen im Punktenamen sind ", . ;", da anhand dieser Zeichen der Datensatz
'aufgetrennt wird.
'Die maximale Anzahl der importierbaren DatensÃ¤tze wird nur durch den vorhandenen Plattenspeicher
'begrenzt.
'---------------------------------------------------------------------------------------
'06.07.2014: Routine CreatePolyLine "+"
'06.07.2014: Routine CreateSpline "+"
'---------------------------------------------------------------------------------------
'TODO-LIST:
'       -- get list of dlnames
'---------------------------------------------------------------------------------------
Option Explicit
   Enum SYMBOL_TYPE
      XCROSS = 1                 'cross which looks like a "X"
      PLUSCROSS                  'cross which looks like a "+"
      UNFILLED_CIRCLE
      TWO_UNFILLED_CONCENTRIC_CIRCLES
      FILLED_CIRCLE
      FILLED_SQUARE
      STAR                       'star which is the union of a 2D marker CROSS ,a 2D marker PLUS and a 2D marker DOT
      DOT
      SMALL_DOT                  'one pixel
      DOWN_ARROW                 'arrow which points to the bottom-left
      UP_ARROW                   'arrow which points to the top-right
      FULL_CIRCLE_BIG
      FULL_SQUARE_BIG
   End Enum
   
'Global vars
   Dim strGS As String                 'the name of the geometric set for the points
   Dim strFS_Sep As String             'the FileSeparator ( / or \ )
   Dim strComma As String              'the 'Comma', may be ';' instead
'   Dim strDecimal As String            'the 'decimal point', may be ',' instead
'---------------------------------------------------------------------------------------
Sub catmain() 'SetPointsFromCVSFile()
' ablauf:
'   - datei auswählen (interaktiv)
'   - part erzeugen / umbenennen
'   - set erzeugen / umbenennen
'   - alle planes ins noshow
'   - achsensystem erzeugen / umbennen
'   - werte zeilenweise aus datei einlesen
'   - strComma bestimmen
'   - punkte setzen
'   - punkte dem set zuweisen
'   - Spline aus den erzeugten Punkten
'   - bildschirm skalieren auf daten
'   - (DLNAMES auslesen)
'   - (speicherort abfragen)
'   - part speichern
'---------------------------------------------------------------------------------------
'vars
   Dim fName As String              'file name (complete path)
   Dim fNameShort As String         'file name w/o path
   Dim fNameTitle As String         'file name w/o ending
   Dim ofName As File               'handle of file for textstream
   Dim strPartDescr As String       'part descriptor (-> part->properties)
   Dim strSaveToPath As String      'just that
   Dim strArr() As String           'array for split
   Dim arrPt() As HybridShapePointCoord 'point array
'---------------------------------------------------------------------------------------

'---------------------------------------------------------------------------------------
'Assign global var values
   strGS = "Assignment_Points"
   strFS_Sep = CATIA.FileSystem.FileSeparator
'   strDecimal = "."                                        'not used
   strComma = ""                                            'init empty
'---------------------------------------------------------------------------------------
'get name of file holding point data
   fName = CATIA.FileSelectionBox("Select CSV-File", "*.csv", CatFileSelectionModeOpen)
'---------------------------------------------------------------------------------------
'check entry
   If fName = "" Then Exit Sub                              'user canceled
   If UCase(Right(fName, 3)) <> "CSV" Then Exit Sub         'wrong ending
'---------------------------------------------------------------------------------------
'split path to get fNameShort, fNameTitle
   Dim i As Integer
   strArr = Split(fName, strFS_Sep)                         'split the path
   fNameShort = strArr(UBound(strArr))                      'use it as the short name
'------------------------------------------------------------------------------------
'create part
   fNameTitle = Left(fNameShort, Len(fNameShort) - 4)       'strip the ending
   strPartDescr = "Points from " & fNameShort
   CreateNewPart fNameTitle, strPartDescr
'---------------------------------------------------------------------------------------
'create point set
   CreateNewGeometricSet                                    'set name is global
'---------------------------------------------------------------------------------------
'hide origin planes
' - hides all planes within the model; hiding origin.planes is more appropriate
   HideAllElements "PLN"
'---------------------------------------------------------------------------------------
'create new axis
   CreateNewAxis "Assignment_Points_Axis"
'---------------------------------------------------------------------------------------
'read data from csv-file and set points
   Set ofName = CATIA.FileSystem.GetFile(fName)             'get the datafile handle
   SetPoints ofName                                         'create the points
'---------------------------------------------------------------------------------------
   CreatePtArray arrPt
'---------------------------------------------------------------------------------------
   CreatePolyLine arrPt                                     'draw polyline
'---------------------------------------------------------------------------------------
   CreateSpline arrPt                                       'create  spline
'---------------------------------------------------------------------------------------
'center data on screen
   CenterAll
'---------------------------------------------------------------------------------------
'get list of DLNames
' not implemented at this moment
'TODO
'---------------------------------------------------------------------------------------
'setting default path to temp dir
   strSaveToPath = CATIA.FileSystem.TemporaryDirectory.Path
'---------------------------------------------------------------------------------------
'save new catpart
   On Error GoTo ErrHandler_SaveAs
   CATIA.ActiveDocument.SaveAs strSaveToPath & strFS_Sep & fNameTitle
   MsgBox "CATPart saved as " & CATIA.ActiveDocument.FullName, vbOKOnly Or vbInformation, "Points Saved To ..."
   
'--------------------------------------------------------------------------------
Exit Sub                                              'don't go thru error handler
'--------------------------------------------------------------------------------
'--------------------------------------------------------------------------------
ErrHandler_SaveAs:
    
    Select Case Err.Number
        Case 91
            MsgBox Err.Number & ": " & Err.Description & " !", vbOKOnly, "SaveAs"
        Case -2147467259
            MsgBox Err.Number & ": " & Err.Description & " !" & vbCrLf & "File not saved!", vbOKOnly, "SaveAs"
        Case Else
            MsgBox Err.Number & ": " & Err.Description, vbOKOnly, "SaveAs"
    End Select
            
'Resume Next                                          'fall thru to quit sub
'--------------------------------------------------------------------------------
End Sub
'---------------------------------------------------------------------------------------

'---------------------------------------------------------------------------------------
'Sub routines
'---------------------------------------------------------------------------------------
'---------------------------------------------------------------------------------------
' Procedure : CreateNewPart
' DateTime  : 15.10.2006 03:37
' Author    : Joseph Herzog
' Purpose   : Create a new CATPart
' Parms     : strPNumber - the partnumber property entry
'           : strDescriptor - the descriptor property entry
'---------------------------------------------------------------------------------------
'
Sub CreateNewPart(strPNumber As String, strDescriptor As String)
   Dim ADoc As Document
   Dim AProduct As Product
   
   Set ADoc = CATIA.Documents.Add("Part")          'create new part
   Set AProduct = CATIA.ActiveDocument.Product
   
   On Error GoTo ErrHandler_CreateNewPart
   
   AProduct.PartNumber = strPNumber                'change partnumber
   AProduct.DescriptionRef = strDescriptor         'add descriptor
   CATIA.ActiveDocument.Part.Update                'update
   CATIA.StatusBar = "Creating New Part!"
Exit Sub
'--------------------------------------------------------------------------------
ErrHandler_CreateNewPart:
    Dim strMsg As String
    
    Select Case Err.Number
'        Case 91
'            strMsg = Err.Number & ": " & Err.Description & " !"
        Case -2147467259
            strMsg = "Error " & Err.Number & ": " & Err.Description & " !" & vbCrLf & "Part not created!"
        Case Else
            strMsg = Err.Number & ": " & Err.Description
    End Select
   MsgBox strMsg, vbOKOnly Or vbCritical, "CreateNewPart"
            
'Resume Next                                          'fall thru to quit sub
'--------------------------------------------------------------------------------

End Sub
'---------------------------------------------------------------------------------------
' Procedure : CreateNewGeometricSet
' DateTime  : 15.10.2006 03:37
' Author    : Joseph Herzog
' Purpose   : create a new geometric set
' Parms     : none; strGS (the set's name)is set globally
'---------------------------------------------------------------------------------------
'
Sub CreateNewGeometricSet()
   Dim HBs As hybridBodies
   Dim gsWireframe As HybridBody
   Dim gsPoints As HybridBody

   Set HBs = CATIA.ActiveDocument.Part.hybridBodies
   Set gsWireframe = HBs.Add                                   'add to list
   gsWireframe.Name = "WireFrame"                                    'rename

   Set gsPoints = HBs.Add                                   'add to list
   gsPoints.Name = strGS                                    'rename
   
   CATIA.StatusBar = "Creating New Set!"
End Sub
'---------------------------------------------------------------------------------------
' Procedure : HideAllElements
' DateTime  : 15.10.2006 03:37
' Author    : Joseph Herzog
' Purpose   : Hides all elements of a given type
' Parms     : strElement - the element type to hide;
'           : valid entries are: PLN, PT, AXS, WIREFRAME and SKETCH;
'---------------------------------------------------------------------------------------
'
Sub HideAllElements(strElement As String)
   Dim strTyp As String
   Dim Sel As Selection

   Select Case strElement
      Case "PLN", "Pln", "pln"
         strTyp = "Plane"
      Case "PT", "Pt", "pt"
         strTyp = "Point"
      Case "WIREFRAME", "Wireframe", "wireframe"
         strTyp = "Wireframe"
      Case "AXS", "Axs", "axs"
         strTyp = "Axis System"
      Case "SKETCH", "Sketch", "sketch"
         strTyp = "Sketch"
      Case Else
         MsgBox "Element typ unknown!", vbOKOnly Or vbCritical, "HideAllElements"
   End Select

   Set Sel = CATIA.ActiveDocument.Selection
   Sel.Clear
   Sel.Search "CATPrtSearch." & strTyp & ",all"
   Sel.VisProperties.SetShow catVisPropertyNoShowAttr
End Sub
'---------------------------------------------------------------------------------------
' Procedure : CreateNewAxis
' DateTime  : 15.10.2006 03:37
' Author    : Joseph Herzog
' Purpose   : Create a new axis system
' Parms     : strAxisName - the axis name
' Note      :  -
'---------------------------------------------------------------------------------------
'Modified: 07.07.2014: removed coordinates

Sub CreateNewAxis(strAxisName As String)
   Dim adp As Part
   Dim axisSystems1 As AxisSystems
   Dim axisSystem1 As AxisSystem
   
   Set adp = CATIA.ActiveDocument.Part
   Set axisSystems1 = adp.AxisSystems
   Set axisSystem1 = axisSystems1.Add()
   adp.UpdateObject axisSystem1
   axisSystem1.IsCurrent = True
   axisSystem1.Name = strAxisName
   adp.Update
End Sub
'---------------------------------------------------------------------------------------
' Procedure : Setpoints
' DateTime  : 15.10.2006 03:38
' Author    : Joseph Herzog
' Purpose   : read the point data, set the points
' Parms     : hFile - handle to the file returned by GetFile
'---------------------------------------------------------------------------------------
'
Sub SetPoints(hFile As File)
   Dim tStream As TextStream
   Dim strText As String
   Dim strArr() As String                                          'no more than 4 entries needed

   Set tStream = hFile.OpenAsTextStream("ForReading")                'open the text stream
   CATIA.StatusBar = "Creating Points!"
   
   Do
      strText = tStream.ReadLine                                     'read the file one line at a time
      If strText = "" Then Exit Do
      If strComma = "" Then SetComma (strText)                       'analyse first line (, or ;)

      strArr = Split(strText, strComma)                              'divide string into parts
                                                                     'set point
      SetPointCoord strArr(0), CDbl(strArr(1)), CDbl(strArr(2)), CDbl(strArr(3))
      DoEvents
   Loop
   tStream.Close                                                     'close text stream
End Sub
'---------------------------------------------------------------------------------------
' Procedure : SplitUp
' DateTime  : 15.10.2006 03:46
' Author    : Joseph Herzog
' Purpose   : Replacement for the VB-Split Command
' Parms     : strToSplit - String that will be divided into parts (input)
'           : strDelim - the character which delimits the single parts (input)
'           : strArray() - the resulting array of strings (output)
'---------------------------------------------------------------------------------------
'
Sub SplitUp(strToSplit As String, strDelim As String, strArray())
   Dim iStart As Integer           'start searching from this position
   Dim iPos  As Integer            'found at this position
   Dim i As Integer                '

   If strToSplit = "" Then Exit Sub
   Do
      iStart = iPos + 1
      iPos = InStr(iStart, strToSplit, strDelim)
      If iPos > 0 Then
         strArray(i) = Mid(strToSplit, iStart, iPos - iStart)
         i = i + 1
      Else  'no more delim found; assign the rest;
            'NOTE: if the last character is a delim, this may not work correctly
         strArray(i) = Mid(strToSplit, iStart, Len(strToSplit) - iStart + 1)
         Exit Do
      End If
      DoEvents
   Loop
End Sub
'---------------------------------------------------------------------------------------
' Procedure : SetPointCoord
' DateTime  : 15.10.2006 03:38
' Author    : Joseph Herzog
' Purpose   : set a point using coordinates; rename point; add to set;
' Parms     : strPt - the point's name
'           : dXVal, dYVal, dZVal - the point's coordinates
'returns    : the new point
'Globals    : strGS - the geometric set name
'---------------------------------------------------------------------------------------
'
Sub SetPointCoord(strPt As String, dXVal As Double, dYVal As Double, dZVal As Double)
   Dim adp As Part
   Dim hSF As HybridShapeFactory
   Dim hB As HybridBody
   Dim hSPtCoord As HybridShapePointCoord
   
   Set adp = CATIA.ActiveDocument.Part
   Set hSF = adp.HybridShapeFactory
   
   Set hB = adp.hybridBodies.Item(strGS)
   Set hSPtCoord = hSF.AddNewPointCoord(dXVal, dYVal, dZVal)               'create point
   hSPtCoord.Name = strPt                                                  'rename
   hB.AppendHybridShape hSPtCoord
   
   adp.Update
'---------------------------------------------------------------------------------------
   Dim oSel As Selection
   Set oSel = CATIA.ActiveDocument.Selection
   oSel.Clear
   oSel.Add hSPtCoord
   oSel.VisProperties.SetSymbolType (SYMBOL_TYPE.STAR)                     '*
   
   SetElementColor hSPtCoord, 255, 255, 0                                  'yellow
   DoEvents
End Sub
Sub CreatePtArray(arrPt)
   Dim adp As Part
   Dim hSF As HybridShapeFactory
   Dim hB As HybridBody
   Dim hSPtCoord As HybridShapePointCoord
   Dim n As Integer
   
   Set adp = CATIA.ActiveDocument.Part
   Set hSF = adp.HybridShapeFactory
   
   Set hB = adp.hybridBodies.Item(strGS)
   
   ReDim arrPt(hB.HybridShapes.Count - 1)
   For n = 1 To hB.HybridShapes.Count
      Set arrPt(n - 1) = hB.HybridShapes.Item(n)
   Next

End Sub

'---------------------------------------------------------------------------------------
' Procedure : CreatePolyLine
' DateTime  : 06.07.2014 01:00
' Author    : Joseph Herzog
' Purpose   : create a polyline using an array of points
' Parms     : arrPt() - point array
'---------------------------------------------------------------------------------------
'
Sub CreatePolyLine(arrPt() As HybridShapePointCoord)
   Dim n As Integer
   Dim adp As Part
   Dim hSPL1 As HybridShapePolyline
   Dim hB1 As HybridBody
   Dim Ref1 As Reference
   
   Set adp = CATIA.ActiveDocument.Part
   Set hSPL1 = adp.HybridShapeFactory.AddNewPolyline()
   Set hB1 = adp.hybridBodies.Item("WireFrame")
   
   For n = 0 To UBound(arrPt)
      Set Ref1 = adp.CreateReferenceFromObject(arrPt(n))
      hSPL1.InsertElement Ref1, n + 1                          'starts at insertion point 1
      hSPL1.SetRadius n + 1, 100                                'set corner radius; values at end are ignored
   Next
   
   hSPL1.Closure = False                                       'do not close
   hB1.AppendHybridShape hSPL1
   hSPL1.Name = "Route_PolyLine"
   adp.Update
'---------------------------------------------------------------------------------------
'das einfärben muss nach dem update stehen!?!
   SetElementColor hSPL1, 0, 0, 255                                  'blue
End Sub

'---------------------------------------------------------------------------------------
' Procedure : CreateSpline
' DateTime  : 06.07.2014 01:00
' Author    : Joseph Herzog
' Purpose   : create a spline using an array of points; no tangents
' Parms     : arrPt() - point array
'---------------------------------------------------------------------------------------
'
Sub CreateSpline(arrPt() As HybridShapePointCoord)
   Dim n As Integer
   
   Dim ad As Document
   Set ad = CATIA.ActiveDocument
   
   Dim adp As Part
   Set adp = ad.Part
   
   Dim hSF1 As factory
   Set hSF1 = adp.HybridShapeFactory
   
   Dim hSSpl1 As HybridShapeSpline
   Set hSSpl1 = hSF1.AddNewSpline()
   
   hSSpl1.SetSplineType 0                                   'cubic spline
   hSSpl1.SetClosing 0                                      'do not close
   
   Dim hBs1 As hybridBodies
   Set hBs1 = adp.hybridBodies

   Dim hB1 As HybridBody
   Set hB1 = hBs1.Item("WireFrame")
   
   Dim Ref1 As Reference
   
   For n = 0 To UBound(arrPt)
      Set Ref1 = adp.CreateReferenceFromObject(arrPt(n))
      hSSpl1.AddPointWithConstraintExplicit Ref1, Nothing, -1#, 1, Nothing, 0#
   Next
   
   hB1.AppendHybridShape hSSpl1
   adp.InWorkObject = hSSpl1
   hSSpl1.Name = "Route_Spline"
   adp.Update
'---------------------------------------------------------------------------------------
'das einfärben muss nach dem update stehen!?!
   SetElementColor hSSpl1, 0, 255, 0                                  'green

End Sub
'---------------------------------------------------------------------------------------
' Procedure : CenterAll
' DateTime  : 15.10.2006 03:38
' Author    : Joseph Herzog
' Purpose   : mimmicks the Fit All In - Command
' Parms     : none
'---------------------------------------------------------------------------------------
'
Sub CenterAll()

'anstelle von startcommand "fit all in" geht auch folgendes:
'   Dim Viewer3D1 As Viewer3D
'   Dim ViewPoint3D1 As Viewpoint3D
'
'   Set Viewer3D1 = CATIA.ActiveWindow.ActiveViewer
'   Viewer3D1.Reframe
'   Set ViewPoint3D1 = Viewer3D1.Viewpoint3D
   
   CATIA.StartCommand "Fit All In"
   CATIA.ActiveDocument.Part.Update                                        'update
   
End Sub
'---------------------------------------------------------------------------------------

'---------------------------------------------------------------------------------------
' Procedure  : SetComma
' DateTime   : 28.10.2006 15:13
' Author     : Joseph Herzog
' Purpose    : Determines if the datafile was written using the english or german lokale
' Comment    : Is the delimiter a ,(english) or a ;(german)
' Parms      : strT - the first data string
' Public vars: strComma - is defined here
' Called by  : SetPoints
' Calls      : --
' Returns    : String
'---------------------------------------------------------------------------------------
Sub SetComma(StrT As String)
   Dim iFirstComma As Integer
   Dim iFirstSemiColon As Integer
   Dim iFirstDecPoint As Integer

   iFirstComma = InStr(StrT, ",")
   iFirstSemiColon = InStr(StrT, ";")
   iFirstDecPoint = InStr(StrT, ".")

   If (iFirstSemiColon > 0) Then
      strComma = ";"                            'probably german
   ElseIf (iFirstComma > 0) Then
      strComma = ","                            'probably english
   End If
End Sub
   
'---------------------------------------------------------------------------------------
' Procedure : SetElementColor
' Author    : jherzog
' Date      : 10.07.2014
' Time      : 03:48
' Languages : VB6 Pro
' V5-Release: V5R19/21
' Purpose   : Set an elements real color
' Parms     : RGB - values
' Ret. Value: -
'
' Syntax    : SetElementColor lR, lG, lB
'
'
'---------------------------------------------------------------------------------------
'
Sub SetElementColor(oElement As Object, lR As Long, lG As Long, lB As Long)

   Dim oSel As Selection
   Set oSel = CATIA.ActiveDocument.Selection
   oSel.Clear
   oSel.Add oElement
   oSel.VisProperties.SetRealColor lR, lG, lB, 0         'no inheritance

End Sub

Sub GetDLNames()
   Dim oSetContr As SettingControllers
   Dim oDLNameNames As DLNameSettingAtt
   Dim arrDLNameList
   Dim sDLName As String
   Dim sUnixPath As String
   Dim sWinPath As String
   Dim sFather  As String
   Dim i As Integer
   
   '  Get the SettingControllers
   Set oSetContr = CATIA.SettingControllers
   
   '  Get the DLNameSettingController
   Set oDLNameNames = oSetContr.Item("CATSysDLNameSettingCtrl")
   
   '  Create a List (Array) with all DL Names defined in the ToolsOptions
   arrDLNameList = oDLNameNames.GetDLNameList()
   For i = 0 To UBound(arrDLNameList)
      sDLName = arrDLNameList(i)
      '  Get the Unix/Windows Path of a special DL Name (sDLName)
      oDLNameNames.GetDLName sDLName, sUnixPath, sWinPath, sFather
      Debug.Print sDLName, sUnixPath, sWinPath
   Next
End Sub
